(setq dd10 1.0  dd11 200.0  dd12 1000.0)
     (setq dd120 (* 1000.0 (/ dd10 dd12)) dd121 (/ dd12 1000.0 dd10)
           dd110 (* 1000.0 (/ dd10 dd11)) dd111 (/ dd11 1000.0 dd10)
     )

坐标初始化：
(defun c:ucs1 ( / x y)
 (setq uusc  (osnap (getpoint "\n坐标点交点:") "Intersection"))
 (command "ucs" "o" uusc)   

    (setq x1 (getpoint  "\n里程桩号起点X<m>,高程标尺起点Y<m>:")
          y1 (cadr x1) x1 (car x1)     y2 (+ y1 (/ dd11 100) )  yy (- (* y2 dd110) (* 85.0 dd10) )
          x (- 0 (*  x1  dd120) )
          y (- 0 (*  y1  dd110) )  y2y2 y
   )
     (command "ucs" "o" (list x y))
     (SETQ x (- 0 x) x (-  x  (* 25.0 dd10)) y (+ (- 0 y) (* 10.0 dd10))  L 0 L1 (* 3.0 dd10)    ) 
     (while (< L 16 )
      (command "textstyle" "style1")
      (command "text"  "j"  "mr"  (list x   y ) L1 "0" (rtos y2 2 1) "")
      (setq L (+ L 1) y2 (+ y2 (/ dd11 100) ) y (+  y   (* 10.0  dd10  )) )
      (print x) (print y)
     )
)

(defun c:ucs2 ( / x y)
 (setq uusc  (osnap (getpoint "\n坐标点交点:") "Intersection"))
 (command "ucs" "o" uusc)   

    (setq x1 (getpoint  "\n行坐标点X<m>,纵坐标点Y<m>:")
          y1 (cadr x1) x1 (car x1)      yy (- (* y1 dd110) (* 60.0 dd10) )
          x (- 0 (*  x1  dd120) )
          y (- 0 (*  y1  dd110) )  
    )
     (command "ucs" "o" (list x y))
)

(defun c:id1 ( )
     (setq p1 (osnap (getpoint "\n选择坐标交点:") "Intersection"))
     (setq x (car p1) y (cadr p1)
           x (* x dd121) 
           y (* y dd111)  
      )     
      (princ "X=") (princ x) (princ "   " )
      (princ "Y=") (princ y) (print " ")
)

(defun  c:zd( / p1 x y x1 y1 yy1 yy2 yy3 yy4 yy5 yy8 yy9 sh dd1)
       (setq p1 (osnap (getpoint "\n地面交点:" ) "Intersection"))
       (setq x (car p1) y (cadr p1)
             x1 (* x dd121)   y1 (* dd111 y)
       )
       (princ "\n覆土深度<m>") (princ sh1) 
       (setq sh (getstring":")) 
       (if (= sh "") (setq sh1 sh1) (setq sh1 (read sh)) )
       (princ "\n设计管径<mm>") (princ dd)
       (setq dd1 (getstring ":"))
       (if (= dd1 "") (setq dd dd) (setq dd (read dd1)) )
       (princ "\n基础深度<m>") (princ ddd)
       (setq ddd1 (getstring ":"))
       (if (= ddd1 "") (setq ddd ddd) (setq ddd (read ddd1)) ) 

        (setq  yy1  x1  yy2 (+ sh1 (/ dd 1000.0) ddd)      yy3 sh1 
               yy4 (- y1 (+ yy3 (/ dd 2000.0  ))) yy5 y1 l1 (* 2.5 dd10)  yy8 (rtos yy1 2 1)
         yy9 (strlen yy8) ) 
      (cond ((= 3 yy9) (setq yy1 (strcat "0+00" yy8)) ) 
            ((= 4 yy9) (setq yy1 (strcat "0+0"  yy8)) )
            ((= 5 yy9) (setq yy1 (strcat "0+"   yy8)) )
 ((= 6 yy9) (setq yy1 (strcat (substr yy8 2 2) "+" (substr yy8 2))) )   )
      (setq xxx (- x (* 1.2 dd10))  yyy (+ yy  (* 1.2 dd10)) )

      (command "textstyle" "style2")
     
      (command "text"  (list xxx  (+ yyy (* 15.0 dd10)) )  l1 "90"           yy1 "")     
      (command "textstyle" "style1")
      
      (command "text"  (list xxx  (+ yyy (* 55.0 dd10)) ) l1 "90" (rtos yy6 2 2) "")
      (command "text"  (list xxx  (+ yyy (* 27.0 dd10)) ) l1 "90" (rtos yy2 2 2) "")     
      (command "text"  (list xxx  (+ yyy (* 37.0 dd10)) ) l1 "90" (rtos yy3 2 2) "")
      (command "text"  (list xxx  (+ yyy (* 45.0 dd10)) ) l1 "90" (rtos yy4 2 2) "")
      (command "text"  (list xxx  (+ yyy (* 65.0 dd10)) ) l1 "90" (rtos yy5 2 2) "")
)

(defun c:el ( / c d el1 el2 el3 el20 el21)
   (setq el1 (getstring "\n管顶(h)/管中心(c)/管底(d)\管径(mm):"))
   (setq el2 (getpoint "\n 坐标点:"))
   (setq c (substr el1 1 1)  d  (/ (read (substr el1 2)) 2000.0) el20 (* (car el2) dd120 ) 
         el21 (* (cadr el2) dd110) el2 (list el20 el21)
   )
  (if (= "c" c) (setq  el3 (list el20  (+ el21 (* d  dd110  ) ) ) ) )
   (if (= "c" c) (command "ellipse" c  el2 el3 (* d dd120 2.0) ) )
  (if (= "d" c) (setq  el3 (list el20  (+ el21 (* d  dd110 2.0 ) ) ) ) )
   (if (= "d" c) (command "ellipse"    el2 el3 (* d dd120 2.0) ) )
  (if (= "h" c) (setq  el3 (list el20  (- el21 (* d  dd110 2.0 ) ) ) ) )
   (if (= "h" c) (command "ellipse"    el2 el3 (* d dd120 2.0) ) ) 
)

地面线绘制：
(defun c:pl1 (  )
     (setq p1 (getpoint "\n地面线开始点(桩号，标高):")) 
     (setq p2 (list 0 0) p3 (list (* (car p1) dd120) (* (cadr p1) dd110)) )      
     (command "line"  p3 (list  (car p3)  (+ yy 75.0 )) "")
     (while (= (type p2) 'list)
           (setq p2 (getpoint "\n地面线结束点(桩号，标高):"))
           
           (setq p4 (list (* (car p2) dd120)  (* (cadr p2) dd110))
           ) 
            (command "pline" p3 "w" "0" "0" p4 "")
            (command "line"  p4 (list  (car p4)  (+ yy 75.0 )) "")
            (setq p3 p4)
       )
)

(defun c:pl2 (  )
     (setq p1 (getpoint "\n地面线开始点(桩号，标高):")) 
     (setq p2 (list 0 0) p3 (list (* (car p1) dd120) (* (cadr p1) dd110)) )      
    
     (while (= (type p2) 'list)
           (setq p2 (getpoint "\n地面线结束点(桩号，标高):"))
           
           (setq p4 (list (* (car p2) dd120)  (* (cadr p2) dd110))
           ) 
            (command "pline" p3 "w" "0" "0" p4 "")
             
            (setq p3 p4)
       )
)

设计参数：设计管道外径＋基础处理深度
(defun  c:sj( )
       (princ "\n 设计管道外径<mm>") (princ dd)
       (setq dd1 (getstring ":"))
       (if (= dd1 "") (setq dd dd) (setq dd (read dd1)) )
       (princ "\n基础处理深度<m>") (princ ddd)
       (setq ddd1 (getstring ":"))
       (if (= ddd1 "") (setq ddd ddd) (setq ddd (read ddd1)) ) 
)

纵断参数4：覆土深度和挖深均相对于设计地面线；
(defun  c:zd4( )
       (princ  "\n纵断参数1：现状地面高程＋设计地面高程＋管底高程＋覆土深度＋挖深＋里程桩号" )
       (setq p1 (osnap (getpoint "\n现状地面交点:" ) "Intersection"))
       (setq x (car p1) y (cadr p1)
             x11 (* x dd121)   y11 (* dd111 y)
       )
       (setq p2 (osnap (getpoint "\n管底交点:" ) "Intersection"))
       (setq x2 (car p2) y2 (cadr p2)
             x21 (* x2 dd121)   y21 (* dd111 y2)
       )
       (setq p3 (osnap (getpoint "\n设计地面交点:" ) "Intersection"))
       (setq x3 (car p3) y3 (cadr p3)
             x31 (* x3 dd121)   y31 (* dd111 y3)
       )
       (setq  yy1  x11    yy6 y31   yy2 (+ (- y31 y21) ddd)   yy3 (- y31 y21     )
              yy4  y21    yy5 y11   L1  (* 3.0 dd10)  
       ) 

      (cond ((<= yy1  -10000.0) (setq  yy8 (- 0 yy1)  yy8 (rtos yy8 2 2)  
                                       yy1 (strcat "K" "-" (substr yy8 1 2) "-" (substr yy8 3)) ) )
            ((<= yy1   -1000.0) (setq  yy8 (- 0 yy1)  yy8 (rtos yy8 2 2)  
                                       yy1 (strcat "K" "-" (substr yy8 1 1) "-" (substr yy8 2)) ) )
            ((<= yy1    -100.0) (setq  yy8 (- 0 yy1)  yy8 (rtos yy8 2 2)  yy1 (strcat "K" "0-"  yy8) ) )
            ((<= yy1     -10.0) (setq  yy8 (- 0 yy1)  yy8 (rtos yy8 2 2)  yy1 (strcat "K" "0-0" yy8) ) )
            ((<  yy1       0.0) (setq  yy8 (- 0 yy1)  yy8 (rtos yy8 2 2)  yy1 (strcat "K" "0-00" yy8) ) )
            ((<  yy1      10.0) (setq  yy8 (rtos yy1 2 2)   yy1 (strcat "K" "0+00" yy8) ) )
            ((<  yy1     100.0) (setq  yy8 (rtos yy1 2 2)   yy1 (strcat "K" "0+0"  yy8) ) )
            ((<  yy1    1000.0) (setq  yy8 (rtos yy1 2 2)   yy1 (strcat "K" "0+"   yy8) ) )
            ((<  yy1   10000.0) (setq  yy8 (rtos yy1 2 2)   
                                       yy1 (strcat "K" (substr yy8 1 1) "+" (substr yy8 2)) ) )
            ((<  yy1  100000.0) (setq  yy8 (rtos yy1 2 2)   
                                       yy1 (strcat "K" (substr yy8 1 2) "+" (substr yy8 3)) ) )
      )

      (setq xxx (- x (* 0.0 dd10))  yyy (+ yy  (* 0.0 dd10)) )
      (command "textstyle" "style2")
      (command "text"  "j"  "mr"  (list xxx  (+ yyy (* 44.0 dd10)) ) L1 "90"       yy1      "")     
      (command "textstyle" "style1")
      (command "text"  "j"  "mr"  (list xxx  (+ yyy (* 74.0 dd10)) ) L1 "90" (rtos yy6 2 2) "")
      
      (command "text"  "j"  "mr"  (list xxx  (+ yyy (* 14.0 dd10)) ) L1 "90" (rtos yy3 2 2) "")
      (command "text"  "j"  "mr"  (list xxx  (+ yyy (* 29.0 dd10)) ) L1 "90" (rtos yy4 2 2) "")
      (command "text"  "j"  "mr"  (list xxx  (+ yyy (* 59.0 dd10)) ) L1 "90" (rtos yy5 2 2) "")      
)

纵断参数1：覆土深度和挖深均相对于设计地面线；
(defun  c:zd1( )
       (princ  "\n纵断参数1：现状地面高程＋设计地面高程＋管底高程＋覆土深度＋挖深＋里程桩号" )
       (setq p1 (osnap (getpoint "\n现状地面交点:" ) "Intersection"))
       (setq x (car p1) y (cadr p1)
             x11 (* x dd121)   y11 (* dd111 y)
       )
       (setq p2 (osnap (getpoint "\n管底交点:" ) "Intersection"))
       (setq x2 (car p2) y2 (cadr p2)
             x21 (* x2 dd121)   y21 (* dd111 y2)
       )
       (setq p3 (osnap (getpoint "\n设计地面交点:" ) "Intersection"))
       (setq x3 (car p3) y3 (cadr p3)
             x31 (* x3 dd121)   y31 (* dd111 y3)
       )
       (setq  yy1  x11    yy6 y31   yy2 (+ (- y31 y21) ddd)   yy3 (- y31 y21 (/ dd 1000.0))
              yy4  y21    yy5 y11   L1  (* 2.4 dd10)  
       ) 

      (cond ((<= yy1  -10000.0) (setq  yy8 (- 0 yy1)  yy8 (rtos yy8 2 1)  
                                       yy1 (strcat "-" (substr yy8 1 2) "-" (substr yy8 3)) ) )
            ((<= yy1   -1000.0) (setq  yy8 (- 0 yy1)  yy8 (rtos yy8 2 1)  
                                       yy1 (strcat "-" (substr yy8 1 1) "-" (substr yy8 2)) ) )
            ((<= yy1    -100.0) (setq  yy8 (- 0 yy1)  yy8 (rtos yy8 2 1)  yy1 (strcat "0-"  yy8) ) )
            ((<= yy1     -10.0) (setq  yy8 (- 0 yy1)  yy8 (rtos yy8 2 1)  yy1 (strcat "0-0" yy8) ) )
            ((<  yy1       0.0) (setq  yy8 (- 0 yy1)  yy8 (rtos yy8 2 1)  yy1 (strcat "0-00" yy8) ) )
            ((<  yy1      10.0) (setq  yy8 (rtos yy1 2 1)   yy1 (strcat "0+00" yy8) ) )
            ((<  yy1     100.0) (setq  yy8 (rtos yy1 2 1)   yy1 (strcat "0+0"  yy8) ) )
            ((<  yy1    1000.0) (setq  yy8 (rtos yy1 2 1)   yy1 (strcat "0+"   yy8) ) )
            ((<  yy1   10000.0) (setq  yy8 (rtos yy1 2 1)   
                                       yy1 (strcat (substr yy8 1 1) "+" (substr yy8 2)) ) )
            ((<  yy1  100000.0) (setq  yy8 (rtos yy1 2 1)   
                                       yy1 (strcat (substr yy8 1 2) "+" (substr yy8 3)) ) )
      )

      (setq xxx (- x (* 0.0 dd10))  yyy (+ yy  (* 0.0 dd10)) )
      (command "textstyle" "style2")
      (command "text"  "j"  "mr"  (list xxx  (+ yyy (* 24.5 dd10)) ) L1 "90"       yy1      "")     
      (command "textstyle" "style1")
      (command "text"  "j"  "mr"  (list xxx  (+ yyy (* 64.5 dd10)) ) L1 "90" (rtos yy6 2 2) "")
      (command "text"  "j"  "mr"  (list xxx  (+ yyy (* 34.5 dd10)) ) L1 "90" (rtos yy2 2 2) "")     
      (command "text"  "j"  "mr"  (list xxx  (+ yyy (* 44.5 dd10)) ) L1 "90" (rtos yy3 2 2) "")
      (command "text"  "j"  "mr"  (list xxx  (+ yyy (* 54.5 dd10)) ) L1 "90" (rtos yy4 2 2) "")
      (command "text"  "j"  "mr"  (list xxx  (+ yyy (* 74.5 dd10)) ) L1 "90" (rtos yy5 2 2) "")      
)

纵断参数2：覆土深度和挖深均相对于设计地面线；
(defun  c:zd2( )
       (princ  "\n纵断参数2：现状地面高程＋设计地面高程＋管中心高程＋覆土深度＋挖深＋里程桩号" )
       (setq p1 (osnap (getpoint  "\n现状地面交点:" ) "Intersection"))
       (setq x (car p1) y (cadr p1)
             x11 (* x dd121)   y11 (* dd111 y)
       )
       (setq p2 (osnap (getpoint "\n管中心交点:" ) "Intersection"))
       (setq x2 (car p2) y2 (cadr p2)
             x21 (* x2 dd121)   y21 (* dd111 y2)
       )
       (setq p3 (osnap (getpoint "\n设计地面交点:" ) "Intersection"))
       (setq x3 (car p3) y3 (cadr p3)
             x31 (* x3 dd121)   y31 (* dd111 y3)
       )
       (setq  yy1 x11   yy6 y31   yy2 (+ (- y31 y21) ddd (/ dd 2000.0))   yy3 (- y31 y21 (/ dd 2000.0))
              yy4 y21   yy5 y11   L1  (* 2.4 dd10)    
       ) 

      (cond ((<= yy1  -10000.0) (setq  yy8 (- 0 yy1)  yy8 (rtos yy8 2 1)  
                                       yy1 (strcat "-" (substr yy8 1 2) "-" (substr yy8 3)) ) )
            ((<= yy1   -1000.0) (setq  yy8 (- 0 yy1)  yy8 (rtos yy8 2 1)  
                                       yy1 (strcat "-" (substr yy8 1 1) "-" (substr yy8 2)) ) )
            ((<= yy1    -100.0) (setq  yy8 (- 0 yy1)  yy8 (rtos yy8 2 1)  yy1 (strcat "0-"  yy8) ) )
            ((<= yy1     -10.0) (setq  yy8 (- 0 yy1)  yy8 (rtos yy8 2 1)  yy1 (strcat "0-0" yy8) ) )
            ((<  yy1       0.0) (setq  yy8 (- 0 yy1)  yy8 (rtos yy8 2 1)  yy1 (strcat "0-00" yy8) ) )
            ((<  yy1      10.0) (setq  yy8 (rtos yy1 2 1)   yy1 (strcat "0+00" yy8) ) )
            ((<  yy1     100.0) (setq  yy8 (rtos yy1 2 1)   yy1 (strcat "0+0"  yy8) ) )
            ((<  yy1    1000.0) (setq  yy8 (rtos yy1 2 1)   yy1 (strcat "0+"   yy8) ) )
            ((<  yy1   10000.0) (setq  yy8 (rtos yy1 2 1)   
                                       yy1 (strcat (substr yy8 1 1) "+" (substr yy8 2)) ) )
            ((<  yy1  100000.0) (setq  yy8 (rtos yy1 2 1)   
                                       yy1 (strcat (substr yy8 1 2) "+" (substr yy8 3)) ) )
      )

      (setq xxx (- x (* 0.0 dd10))  yyy (+ yy  (* 0.0 dd10)) )
      (command "textstyle" "style2")
      (command "text"  "j"  "mr"  (list xxx  (+ yyy (* 24.5 dd10)) ) L1 "90"       yy1      "")     
      (command "textstyle" "style1")
      (command "text"  "j"  "mr"  (list xxx  (+ yyy (* 64.5 dd10)) ) L1 "90" (rtos yy6 2 2) "")
      (command "text"  "j"  "mr"  (list xxx  (+ yyy (* 34.5 dd10)) ) L1 "90" (rtos yy2 2 2) "")     
      (command "text"  "j"  "mr"  (list xxx  (+ yyy (* 44.5 dd10)) ) L1 "90" (rtos yy3 2 2) "")
      (command "text"  "j"  "mr"  (list xxx  (+ yyy (* 54.5 dd10)) ) L1 "90" (rtos yy4 2 2) "")
      (command "text"  "j"  "mr"  (list xxx  (+ yyy (* 74.5 dd10)) ) L1 "90" (rtos yy5 2 2) "")      
)

纵断参数3：覆土深度相对于设计地面线；挖深相对于现状地面线；
(defun  c:zd3( )
       (princ  "\n纵断参数2：现状地面高程＋设计地面高程＋管中心高程＋覆土深度＋挖深＋里程桩号" )
       (setq p1 (osnap (getpoint  "\n现状地面交点:" ) "Intersection"))
       (setq x (car p1) y (cadr p1)
             x11 (* x dd121)   y11 (* dd111 y)
       )
       (setq p2 (osnap (getpoint "\n管中心交点:" ) "Intersection"))
       (setq x2 (car p2) y2 (cadr p2)
             x21 (* x2 dd121)   y21 (* dd111 y2)
       )
       (setq p3 (osnap (getpoint "\n设计地面交点:" ) "Intersection"))
       (setq x3 (car p3) y3 (cadr p3)
             x31 (* x3 dd121)   y31 (* dd111 y3)
       )
       (setq  yy1 x11   yy6 y31   yy2 (+ (- y11 y21) ddd (/ dd 2000.0))   yy3 (- y31 y21 (/ dd 2000.0))
              yy4 y21   yy5 y11   L1  (* 2.4 dd10)    
       ) 

      (cond ((<= yy1  -10000.0) (setq  yy8 (- 0 yy1)  yy8 (rtos yy8 2 1)  
                                       yy1 (strcat "-" (substr yy8 1 2) "-" (substr yy8 3)) ) )
            ((<= yy1   -1000.0) (setq  yy8 (- 0 yy1)  yy8 (rtos yy8 2 1)  
                                       yy1 (strcat "-" (substr yy8 1 1) "-" (substr yy8 2)) ) )
            ((<= yy1    -100.0) (setq  yy8 (- 0 yy1)  yy8 (rtos yy8 2 1)  yy1 (strcat "0-"  yy8) ) )
            ((<= yy1     -10.0) (setq  yy8 (- 0 yy1)  yy8 (rtos yy8 2 1)  yy1 (strcat "0-0" yy8) ) )
            ((<  yy1       0.0) (setq  yy8 (- 0 yy1)  yy8 (rtos yy8 2 1)  yy1 (strcat "0-00" yy8) ) )
            ((<  yy1      10.0) (setq  yy8 (rtos yy1 2 1)   yy1 (strcat "0+00" yy8) ) )
            ((<  yy1     100.0) (setq  yy8 (rtos yy1 2 1)   yy1 (strcat "0+0"  yy8) ) )
            ((<  yy1    1000.0) (setq  yy8 (rtos yy1 2 1)   yy1 (strcat "0+"   yy8) ) )
            ((<  yy1   10000.0) (setq  yy8 (rtos yy1 2 1)   
                                       yy1 (strcat (substr yy8 1 1) "+" (substr yy8 2)) ) )
            ((<  yy1  100000.0) (setq  yy8 (rtos yy1 2 1)   
                                       yy1 (strcat (substr yy8 1 2) "+" (substr yy8 3)) ) )
      )

      (setq xxx (- x (* 0.0 dd10))  yyy (+ yy  (* 0.0 dd10)) )
      (command "textstyle" "style2")
      (command "text"  "j"  "mr"  (list xxx  (+ yyy (* 24.5 dd10)) ) L1 "90"       yy1      "")     
      (command "textstyle" "style1")
      (command "text"  "j"  "mr"  (list xxx  (+ yyy (* 64.5 dd10)) ) L1 "90" (rtos yy6 2 2) "")
      (command "text"  "j"  "mr"  (list xxx  (+ yyy (* 34.5 dd10)) ) L1 "90" (rtos yy2 2 2) "")     
      (command "text"  "j"  "mr"  (list xxx  (+ yyy (* 44.5 dd10)) ) L1 "90" (rtos yy3 2 2) "")
      (command "text"  "j"  "mr"  (list xxx  (+ yyy (* 54.5 dd10)) ) L1 "90" (rtos yy4 2 2) "")
      (command "text"  "j"  "mr"  (list xxx  (+ yyy (* 74.5 dd10)) ) L1 "90" (rtos yy5 2 2) "")      
)

坡度绘制：
(defun  c:pd( )
       (setq p1 (osnap (getpoint "\n第一个拐点:" ) "Intersection"))
       (setq x (car p1) y (cadr p1)
             x11 (* x dd121)   y11 (* dd111 y)  
       )
       (setq p2 (osnap (getpoint "\n第二个拐点:" ) "Intersection"))
       (setq x2 (car p2) y2 (cadr p2)
             x21 (* x2 dd121)   y21 (* dd111 y2)
       )
      (if (< y11 y21) (setq p11 (list x (+ yy (* -15.0 dd10)))  p12 (list x2 (+ yy (* -0.0 dd10))) 
                        dst1   (- y21 y11)    )
                      (setq p11 (list x (+ yy (* -0.0 dd10)))  p12 (list x2 (+ yy (* -15.0 dd10))) 
                        dst1   (- y11 y21)   )
      )
      (setq st11   (- x21 x11)   st12 (* (/ dst1 st11) 1000.0) st13 (sqrt (+ (* st11 st11) (* dst1 dst1)))   
            st15 (+ x (/ (* st11  dd120) 2.0))   )
      (command "line"  p11  p12 "")
      (if (< y11 y21) (setq p13 (list st15  (+ yy (*  -5.0 dd10)) )
                            p14 (list st15  (+ yy (*  -10.0 dd10)) )
                      )
                      (setq p13 (list st15 (+ yy (*  -5.0 dd10)) )
                            p14 (list (- st15 (* 0.0 dd10)) (+ yy (*  -10.0 dd10)) )
                      )
      ) 
      (if (< y11 y21) (
                      (command "text"  "j"  "r"  p13 L1 "0" (rtos st12 2 2) "")
                      (command "text"  "j"  "tl"  p14 L1 "0" (rtos st11 2 1) "")
                      )
                      (
                      (command "text"  p13 l1 "0" (rtos st12 2 2) "")
                      (command "text"  "j"  "tr"  p14 L1 "0" (rtos st11 2 1) "")
                      )
      )
)
